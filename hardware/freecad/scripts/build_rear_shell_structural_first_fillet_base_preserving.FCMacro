"""Rebuild support/web features while preserving the source shell base.

The base shape is copied from the prior disposable hybrid candidate, whose
BaseShell is the saved Body002FullWidthSeat output. This avoids re-adding the
six-circle RearMountReinforcement Pad because that native Pad already appears
in the protected rear Tip's upstream ancestry. New boss/web operations are
native PartDesign features. The R0.25 edge finish follows the support chain;
shallow anti-slip seats follow the edge finish.

Run in FreeCAD. PENDANT_CAD_REVIEW_OUTPUT may select a new destination. Existing
files are never overwritten. The protected monolith and production assembly
are opened read-only and never saved.
"""
import json
import os
from pathlib import Path

import FreeCAD as App
import MeshPart


REPO = Path(__file__).resolve().parents[3]
SOURCE = REPO / "hardware/freecad/pendant-bodies/rear-shell-recovered-screw-pad-review-candidate-2026-10-31.FCStd"
DEFAULT_OUTPUT = REPO / "hardware/freecad/pendant-bodies/rear-shell-structural-first-fillet-no-duplicate-pad-2026-10-31.FCStd"
OUTPUT = Path(os.environ.get("PENDANT_CAD_REVIEW_OUTPUT", str(DEFAULT_OUTPUT))).expanduser().resolve()

if OUTPUT.exists():
    raise FileExistsError("Refusing to overwrite review candidate: %s" % OUTPUT)
if not SOURCE.exists():
    raise FileNotFoundError("Missing review source: %s" % SOURCE)

src = App.openDocument(str(SOURCE))
src.recompute()
doc = App.newDocument("rear_shell_structural_first_no_duplicate_pad")
body = doc.addObject("PartDesign::Body", "RearShellStructuralFirstNoDuplicatePad")
body.Label = "Rear shell — preserve base reinforcement, rebuild supports"

base = body.newObject("PartDesign::Feature", "CleanRearShellBase")
base.Label = "Clean rear shell base (already includes original mount reinforcement)"
base.Shape = src.getObject("BaseShell").Shape.copy()
doc.recompute()


def clone_sketch(source, name, label):
    sketch = doc.addObject("Sketcher::SketchObject", name)
    body.addObject(sketch)
    sketch.Label = label
    sketch.Placement = source.Placement
    for index, geometry in enumerate(source.Geometry):
        sketch.addGeometry(geometry, source.getConstruction(index))
    for constraint in source.Constraints:
        sketch.addConstraint(constraint)
    if getattr(source, "ExternalGeometryCount", 0):
        raise RuntimeError("Refusing to clone sketch with external geometry: %s" % source.Name)
    doc.recompute()
    if sketch.GeometryCount != source.GeometryCount or len(sketch.Constraints) != len(source.Constraints):
        raise RuntimeError("Sketch clone is incomplete: %s" % source.Name)
    return sketch


def add_pad(source_feature, source_sketch, name, label):
    sketch = clone_sketch(source_sketch, name + "Profile", label + " profile")
    feature = body.newObject("PartDesign::Pad", name)
    feature.Label = label
    feature.Profile = sketch
    feature.Length = source_feature.Length.Value
    feature.Reversed = source_feature.Reversed
    feature.Refine = True
    doc.recompute()
    if feature.Shape.isNull() or not feature.Shape.isValid() or len(feature.Shape.Solids) != 1:
        raise RuntimeError("Pad failed to produce one valid solid: %s" % name)
    return feature


def add_pocket(source_feature, source_sketch, name, label):
    sketch = clone_sketch(source_sketch, name + "Profile", label + " profile")
    feature = body.newObject("PartDesign::Pocket", name)
    feature.Label = label
    feature.Profile = sketch
    feature.Length = source_feature.Length.Value
    feature.Reversed = source_feature.Reversed
    feature.Refine = True
    doc.recompute()
    if feature.Shape.isNull() or not feature.Shape.isValid() or len(feature.Shape.Solids) != 1:
        raise RuntimeError("Pocket failed to produce one valid solid: %s" % name)
    return feature


last = base
for pad_name, sketch_name in (
    ("UpperLeftSupportPad", "UpperLeftProfile"),
    ("UpperRightSupportPad", "UpperRightProfile"),
    ("LowerLeftSupportPad", "LowerLeftProfile"),
    ("LowerRightSupportPad", "LowerRightProfile"),
):
    source_feature = src.getObject(pad_name)
    last = add_pad(source_feature, src.getObject(sketch_name), "FinishOrder_" + pad_name,
                   "Finish-order " + source_feature.Label)

last = add_pocket(src.getObject("RearM2PassageClearance"),
                  src.getObject("RearM2PassageClearanceSketch"),
                  "FinishOrder_M2Passages", "Six M2 passages")

for pad_name, sketch_name in (
    ("LowerLeftInnerWebPad", "LowerLeftInnerWebProfile"),
    ("LowerRightInnerWebPad", "LowerRightInnerWebProfile"),
):
    source_feature = src.getObject(pad_name)
    last = add_pad(source_feature, src.getObject(sketch_name), "FinishOrder_" + pad_name,
                   "Finish-order " + source_feature.Label)

pre_fillet = last.Shape.Volume
face_candidates = []
for face_index, face in enumerate(last.Shape.Faces, 1):
    try:
        u0, u1, v0, v1 = face.ParameterRange
        normal = face.normalAt((u0 + u1) / 2.0, (v0 + v1) / 2.0)
        if normal.z < -0.99 and face.Area > 1000.0:
            face_candidates.append((face.Area, face_index, face, normal))
    except Exception:
        continue
if not face_candidates:
    raise RuntimeError("No broad downward-facing contact face found")
face_candidates.sort(key=lambda item: item[0], reverse=True)
face_area, face_index, face, normal = face_candidates[0]
edge_names = []
for edge_index, edge in enumerate(last.Shape.Edges, 1):
    if any(edge.isSame(wire_edge) for wire_edge in face.OuterWire.Edges):
        edge_names.append("Edge%d" % edge_index)
if len(edge_names) != 19:
    raise RuntimeError("Expected 19 perimeter edges; found %d" % len(edge_names))

fillet = body.newObject("PartDesign::Fillet", "StructuralFirstBottomPerimeterFinish")
fillet.Label = "Bottom perimeter edge break R0.25 — after structural supports"
fillet.Base = (last, edge_names)
fillet.Radius = 0.25
fillet.Refine = True
doc.recompute()
if fillet.Shape.isNull() or not fillet.Shape.isValid() or len(fillet.Shape.Solids) != 1:
    raise RuntimeError("R0.25 fillet failed after support geometry")

seat_source = src.getObject("AntiSlipSeatPocket")
seat_sketch = clone_sketch(src.getObject("AntiSlipSeatProfiles"),
                           "FinishOrder_AntiSlipSeatProfiles", "Shallow crescent seat profiles")
seat = body.newObject("PartDesign::Pocket", "FinishOrder_AntiSlipSeatPocket")
seat.Label = "Shallow anti-slip seats — after structural finish"
seat.Profile = seat_sketch
seat.Length = seat_source.Length.Value
seat.Reversed = seat_source.Reversed
seat.Refine = True
doc.recompute()
body.Tip = seat
if seat.Shape.isNull() or not seat.Shape.isValid() or len(seat.Shape.Solids) != 1:
    raise RuntimeError("Final shell did not recompute as one valid solid")

doc.saveAs(str(OUTPUT))
final_volume = seat.Shape.Volume
result = {
    "output": str(OUTPUT),
    "body": body.Name,
    "tip": body.Tip.Name,
    "tip_volume_mm3": final_volume,
    "solid_count": len(seat.Shape.Solids),
    "valid": seat.Shape.isValid(),
    "pre_fillet_volume_mm3": pre_fillet,
    "fillet_removed_mm3": pre_fillet - fillet.Shape.Volume,
    "fillet_radius_mm": fillet.Radius.Value,
    "fillet_source_face_area_mm2": face_area,
    "fillet_source_normal": [normal.x, normal.y, normal.z],
    "fillet_edges": edge_names,
    "seat_pocket_depth_mm": seat.Length.Value,
}
print(json.dumps(result, indent=2))
App.closeDocument(doc.Name)
App.closeDocument(src.Name)

# Cold reopen and recompute the saved candidate before reporting success.
check_doc = App.openDocument(str(OUTPUT))
check_doc.recompute()
check_body = check_doc.getObject("RearShellStructuralFirstNoDuplicatePad")
check_shape = check_body.Tip.Shape
mesh = MeshPart.meshFromShape(Shape=check_shape, LinearDeflection=0.08,
                              AngularDeflection=0.35, Relative=False)
if not check_shape.isValid() or len(check_shape.Solids) != 1 or not mesh.isSolid():
    raise RuntimeError("Cold-open candidate failed solid or mesh closure checks")
print(json.dumps({
    "cold_reopen_tip": check_body.Tip.Name,
    "state": list(check_body.Tip.State),
    "valid": check_shape.isValid(),
    "solid_count": len(check_shape.Solids),
    "volume_mm3": check_shape.Volume,
    "mesh_closed": mesh.isSolid(),
    "mesh_facets": len(mesh.Facets),
}, indent=2))
App.closeDocument(check_doc.Name)
